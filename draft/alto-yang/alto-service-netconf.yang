module alto-service-netconf {
  yang-version 1;
  
  namespace "urn:ietf:params:xml:ns:yang:alto-service-netconf";
  // TODO: replace with IANA namespace when assigned

  prefix "alto-netconf";

  import alto-service-types {
    prefix alto;
  }

  import alto-service-did {
    prefix as-did;
  }

  organization "ALTO WG";
  contact "alto@ietf.org";

  description 
    "This module defines the netconf version of alto services. This is
    not compliant/interoperable with RFC7285";

  revision 2014-11-01 {
    description "Initial version.";
  }


  /****************************************************
     DATA INSTANCES of all ALTO information resources

     unfiltered network-maps, unfiltered cost-maps are all instances
     of resources. IRD is also modeled as data.

     The design uses augment as the basic approach to implement
     inheritance.
   ****************************************************/

  container resources {
    config false;
    uses as-did:alto-resources;
  }

  /************************************
   * RPCs                             *
   ************************************/

  rpc endpoint-cost-service {
    description
      "ReqEndpointCostMap. RFC7285 Sec. 11.5.1.3." +
      " object {
          CostType          cost-type;
          [JSONString       constraints<0..*>;]
          EndpointFilter    endpoints;
        } ReqEndpointCostMap;";
    input {
      container cost-type {
        must "current()";
        uses alto:cost-type;
      }
      leaf-list constraints {
        type alto:constraint;
        description
          "RFC7285 Sec. 11.5.1.3.";
      }
      container endpoints {
        must "current()";
        leaf-list srcs {
          type alto:typed-endpoint-address;
          description
            "Source endpoint addresses.";
        }
        leaf-list dsts {
          type alto:typed-endpoint-address;
          description
            "Destination endpoint addresses.";
        }
        description
          " EndpointFilter: Endpoint addr. RFC7285 Sec. 11.5.1.3." +
          " object {
              [TypedEndpointAddr srcs<0..*>;]
              [TypedEndpointAddr dsts<0..*>;]
            } EndpointFilter;";
      }
    }
    output {
      container endpoint-cost-service {
        container meta {
          container cost-type {
            uses alto:cost-type;
          }
        }
        list endpoint-cost-map {
          leaf src {
            type alto:typed-endpoint-address;
            description
              "Source endpoint address.";
          }
          key "src";
          list dst-costs {
            leaf dst {
              type alto:typed-endpoint-address;
              description
                "Destination endpoint address.";
            }
            key "dst";
            uses alto:alto-cost {
              description
                "Cost from source to destination.";
            }
            description
              "The list represents the inner part of the cost matrix." +
              "EndpointDstCosts. RFC7285 Sec. 11.5.1.6." +
              " object-map {
                  TypedEndpointAddr -> JSONValue;
                } EndpointDstCosts;";
          }
          description
            "The list represents the outer part of the cost matrix." +
            "EndpointCostMapData. RFC7285 Sec. 11.5.1.6." +
            " object {
                EndpointCostMapData endpoint-cost-map;
              } InfoResourceEndpointCostMap : ResponseEntityBase;
              object-map {
                TypedEndpointAddr -> EndpointDstCosts;
              } EndpointCostMapData;";
        }
      }
    }
  }

}
