module alto-service-rpc {
  yang-version 1;
  
  namespace "urn:ietf:params:xml:ns:yang:alto-service-rpc";
  // TODO: replace with IANA namespace when assigned

  prefix "as-rpc";

  import alto-service-types {
    prefix alto;
  }

  organization "ALTO WG";
  contact "alto@ietf.org";

  description 
    "This module defines the RPCs for a semantically equivalent
    data model for the ALTO services defined in RFC7285.";

  revision 2014-11-09 {
    description "Change rpc inputs for full/filtered map services.";
  }

  revision 2014-11-01 {
    description "Importing from alto-service-types.";
  }

  revision 2014-10-24 {
    description "Initial version.";
  }

  /************************************
   * RPCs                             *
   ************************************/

  rpc IRD-service {
    output {
      container IRD-service {
        uses alto:IRD;
      }
    }
  }

  rpc network-map-service {
    output {
      container network-map-service {
        uses alto:network-map;
      }
    }
  }

  rpc cost-map-service {
    output {
      container cost-map-service {
        uses alto:cost-map;
      }
    }
  }

  rpc filtered-network-map-service {
    description
      "inquiries on filtered network map" +
      "ReqFilteredNetworkMap. RFC7285 Sec. 11.3.1.3." +
        " object {
            PIDName pids<0..*>;
            [AddressType address-types<0..*>;]
          } ReqFilteredNetworkMap;";
    input {
      leaf-list pids {
        must "current()";
        type alto:pid-name;
      }
      leaf-list address-types {
        type alto:endpoint-address-type;
      }
    }
    output {
      container filtered-network-map-service {
        uses alto:network-map;
      }
    }
  }

  rpc filtered-cost-map-service {
    input {
      container cost-type {
        must "current()";
        uses alto:cost-type;
      }
      leaf-list constraints {
        type alto:constraint;
        description
          "RFC7285 Sec. 11.3.2.3.";
      }
      container pids {
        leaf-list srcs {
          type alto:pid-name;
          description
            "Source endpoint addresses.";
        }
        leaf-list dsts {
          type alto:pid-name;
          description
            "Destination endpoint addresses.";
        }
        description
          "PIDFilter: Endpoint addresses. RFC7285 Sec. 11.3.2.3." +
          " object {
              PIDName srcs<0..*>;
              PIDName dsts<0..*>;
            } PIDFilter;";
      }
    }
    output {
      container filtered-cost-map-service {
        uses alto:cost-map;
      }
    }
  }

  rpc endpoint-property-service {
    description
      "inquiries on properties of an endpoint" +
      " object {
            EndpointPropertyType  properties<1..*>;
            TypedEndpointAddr     endpoints<1..*>;
          } ReqEndpointProp;";
    input {
      leaf-list properties {
        type alto:endpoint-property-type;
        min-elements 1;
      }
      leaf-list endpoints {
        type alto:typed-endpoint-address;
        min-elements 1;
      }
    }
    output {
      container endpoint-property-service {
        uses alto:endpoint-property-map;
      }
    }
  }


  rpc endpoint-cost-service {
    description
      "ReqEndpointCostMap. RFC7285 Sec. 11.5.1.3." +
      " object {
          CostType          cost-type;
          [JSONString       constraints<0..*>;]
          EndpointFilter    endpoints;
        } ReqEndpointCostMap;";
    input {
      container cost-type {
        must "current()";
        uses alto:cost-type;
      }
      leaf-list constraints {
        type alto:constraint;
        description
          "RFC7285 Sec. 11.5.1.3.";
      }
      container endpoints {
        must "current()";
        leaf-list srcs {
          type alto:typed-endpoint-address;
          description
            "Source endpoint addresses.";
        }
        leaf-list dsts {
          type alto:typed-endpoint-address;
          description
            "Destination endpoint addresses.";
        }
        description
          " EndpointFilter: Endpoint addr. RFC7285 Sec. 11.5.1.3." +
          " object {
              [TypedEndpointAddr srcs<0..*>;]
              [TypedEndpointAddr dsts<0..*>;]
            } EndpointFilter;";
      }
    }
    output {
      container endpoint-cost-service {
        container meta {
          container cost-type {
            uses alto:cost-type;
          }
        }
        list endpoint-cost-map {
          leaf src {
            type alto:typed-endpoint-address;
            description
              "Source endpoint address.";
          }
          key "src";
          list dst-costs {
            leaf dst {
              type alto:typed-endpoint-address;
              description
                "Destination endpoint address.";
            }
            key "dst";
            uses alto:alto-cost {
              description
                "Cost from source to destination.";
            }
            description
              "The list represents the inner part of the cost matrix." +
              "EndpointDstCosts. RFC7285 Sec. 11.5.1.6." +
              " object-map {
                  TypedEndpointAddr -> JSONValue;
                } EndpointDstCosts;";
          }
          description
            "The list represents the outer part of the cost matrix." +
            "EndpointCostMapData. RFC7285 Sec. 11.5.1.6." +
            " object {
                EndpointCostMapData endpoint-cost-map;
              } InfoResourceEndpointCostMap : ResponseEntityBase;
              object-map {
                TypedEndpointAddr -> EndpointDstCosts;
              } EndpointCostMapData;";
        }
      }
    }
  }
}
