module alto-service-restconf {
  yang-version 1;
  
  namespace "urn:ietf:params:xml:ns:yang:alto-service-restconf";
  // TODO: replace with IANA namespace when assigned

  prefix "alto-restconf";

  import alto-service-types {
    prefix alto;
  }

  import alto-service-did {
    prefix alto-did;
  }

  organization "ALTO WG";
  contact "alto@ietf.org";

  description 
    "This module defines a data model for the ALTO services
     using restconf. Note this is not interop with RFC7285.";

  revision 2014-11-01 {
    description "Initial version.";
  }

  /************************************
   * Data Instances                   *
   ************************************/

  container resources {
    config false;
    uses alto-did:alto-resources;
  }

  /************************************
   * RPCs                             *
   ************************************/

  rpc filtered-network-map-service {
    input {
      leaf-list pids {
        must "current()";
        type alto:pid-name;
      }
      leaf-list address-types {
        type alto:endpoint-address-type;
      }
    }
    output {
      container filtered-network-map-service {
        uses alto:network-map;
      }
    }
  }

  rpc filtered-cost-map-service {
    input {
      container cost-type {
        must "current()";
        uses alto:cost-type;
      }
      leaf-list constraints {
        type alto:constraint;
      }
      container pids {
        leaf-list srcs {
          type alto:pid-name;
        }
        leaf-list dsts {
          type alto:pid-name;
        }
      }
    }
    output {
      container filtered-cost-map-service {
        uses alto:cost-map;
      }
    }
  }

  rpc endpoint-property-service {
    input {
      leaf-list properties {
        type alto:endpoint-property-type;
        min-elements 1;
      }
      leaf-list endpoints {
        type alto:typed-endpoint-address;
        min-elements 1;
      }
    }
    output {
      container endpoint-property-service {
        uses alto:endpoint-property-map;
      }
    }
  }

  rpc endpoint-cost-service {
    input {
      container cost-type {
        must "current()";
        uses alto:cost-type;
      }
      leaf-list constraints {
        type alto:constraint;
      }
      container endpoints {
        must "current()";
        leaf-list srcs {
          type alto:typed-endpoint-address;
        }
        leaf-list dsts {
          type alto:typed-endpoint-address;
        }
      }
    }
    output {
      container endpoint-cost-service {
        container meta {
          container cost-type {
            uses alto:cost-type;
          }
        }
        list endpoint-cost-map {
          leaf src {
            type alto:typed-endpoint-address;
          }
          key "src";
          list dst-costs {
            leaf dst {
              type alto:typed-endpoint-address;
            }
            key "dst";
            uses alto:alto-cost;
          }
        }
      }
    }
  }

}
