module alto-service-inheritance {
  yang-version 1;
  
  namespace "urn:ietf:params:xml:ns:yang:alto-service";
  // TODO: replace with IANA namespace when assigned

  prefix "as";

  import ietf-inet-types {
    prefix inet;
  }

  /*
  // currently unused
  import ietf-yang-types {
    prefix yang;
  }
  */

  organization "ALTO WG";
  contact "alto@ietf.org";

  description 
    "This module defines a data model for the ALTO services
     defined in RFC7285.";

  revision 2014-10-09 {
    description "v1. pending review";
  }

  revision 2014-09-24 {
    description "Initial revision. betw Michael and Xiao";
  }
  
  /********************
   * TYPE DEFINITIONS *
   ********************/

  typedef endpoint-address {
    type union {
      type string {
        pattern
          'ipv4:(([0-9]|[1-9][0-9]|1[0-9][0-9]|2[0-4][0-9]|25[0-5])\.){3}'
        +  '([0-9]|[1-9][0-9]|1[0-9][0-9]|2[0-4][0-9]|25[0-5])'
        + '(%[\p{N}\p{L}]+)?';
        //ref: ietf-inet-types.yang ipv6-address
      }
      type string {
        pattern 'ipv6:((:|[0-9a-fA-F]{0,4}):)([0-9a-fA-F]{0,4}:){0,5}'
              + '((([0-9a-fA-F]{0,4}:)?(:|[0-9a-fA-F]{0,4}))|'
              + '(((25[0-5]|2[0-4][0-9]|[01]?[0-9]?[0-9])\.){3}'
              + '(25[0-5]|2[0-4][0-9]|[01]?[0-9]?[0-9])))'
              + '(%[\p{N}\p{L}]+)?';
        pattern 'ipv6:(([^:]+:){6}(([^:]+:[^:]+)|(.*\..*)))|'
              + '((([^:]+:)*[^:]+)?::(([^:]+:)*[^:]+)?)'
              + '(%.+)?';
      }
      // EXTENSION: additional address types will be added here.
    }
    description
      "Ref: RFC7285 Sec. 10.4.1 Typed Endpoint Addresses" +
      "= AddressType:EndpointAddr" +
      "TODO: restrict both halves of the address. See TODO.txt for" +
      "explanation of difficulty. The second half should extend the" +
      "restrictions if the first half (AddressType is ipv4 or" +
      "ipv6). Ref: RFC7285 10.4.2.";
  }

  typedef endpoint-address-type {
    type union {
      type enumeration {
        enum ipv4;
        enum ipv6;
      }
      type string {
        pattern "[0-9a-zA-Z]+";
      }
    }
    description
      "If the address is not typed, it has an associated address type." +
      "Ref: RFC7285 Sec 2.2.";
  }

  typedef endpoint-prefix {
    type inet:ip-prefix;
  }
  
  grouping endpoint-address-group {
    description
      "EndpointAddrGroup. RFC7285 Sec. 10.4.5." +
      " object-map {
          AddressType -> endpoint-prefix<0..*>;
        } EndpointAddrGroup;";
    list endpoint-address-group { /* yry: issue: json encoding will not generate map, but an array */
      key address-type;
      leaf address-type {
        type endpoint-address-type;
      }
      leaf-list endpoint-prefix {
        type endpoint-prefix;
      }
      /* TODO:
      must
        "address-type != 'ipv4' or " +
        "(address-type = 'ipv4' and endpoint-prefix matches inet:ipv4-prefix)" {
        error-message "Invalid ipv4 address.";
      }
      must
        "address-type != 'ipv6' or " +
        "(address-type = 'ipv6' and endpoint-prefix = 'inet:ipv6-prefix')" {
        error-message "Invalid ipv6 address.";
      }
      */
    }
  }

  grouping endpoint-addresses {
    leaf-list endpoints {  /* yry: Can the list be a mix of ipv4 and ipv6 addresses?
                              One possibility of typed branch is to define ipv4 addresses and ipv6 addresses.
                              sx: yes. see typedef endpoint-address, it is a union of ipv4 and ipv6, could be either.*/
      type endpoint-address;
      description
        "The leaf list identifies endpoints.";
    }
  }

  typedef network-location {
    type union {
      type inet:ipv4-prefix;
      type inet:ipv6-prefix;
      type inet:ipv4-address;
      type inet:ipv6-address;
    }
    description
      "Network location, either IPv4 or Ipv6.";
  }

  grouping network-locations {
    leaf-list locations {    /* yry: this will allow a mixed type of addresses. */
      type network-location;
      description
        "The leaf list identifies network locations.";
    }
    description
      "This corresponds to the term __Network Location__ in RFC7285 Sec. 2.3";
  }

  typedef valid-id-string {
    type string {
      length "1..64";
      pattern "[0-9a-zA-Z_\-:@\.]+";
    }
  }

  typedef pid-name {
    type valid-id-string;
    description
      "Name for the PID." +
      "RFC7285, Section 10.1. Note: the '.' separator MUST NOT be" +
      "used unless specifically indicated in RFC7285 or an extension" +
      "document.";
  }

  typedef cost-metric {
    type union {
      type enumeration {
        enum routingcost {
          value "0"; /* yry: what is the implication on encoding? */
          description
          "Default metric. MUST support. RFC7285 Sec. 6.1.1.1.";
        }
        enum hopcount {
          value "1";
          description
          "Hopcount metric.";
        }
        // EXTENSION: Additional cost-metric will be defined here.
      }
      type string {
        length 1..32;
        pattern "[\w\-:\.]+";
      }
    }
    description
      "Cost metric. for type string, 'priv:' reserved for Private Use.";
  }

  typedef cost-mode {
    type enumeration {
      enum numerical {
        value "0";
        description
          "Numerical cost mode.";
      }
      enum ordinal {
        value "1";
        description
          "Ordinal cost mode.";
      }
      // EXTENSION: Additional cost-mode will be defined here.
    }
    description
      "Cost mode. MUST support at least one of numerical and ordinal";
  }

  typedef cost-type-name {
    type string;
    // no specification in RFC7285, looks like alphanumeric and dash.
  }

  // yry: distinguish cost-type definition (used in ird), which includes cost-mode, cost-metric, and description
  //                  cost-type value (used in cost map), which includes only cost-mode and cost-metric
  grouping cost-type {
    /* yry: This is in IRD only, right? How about name cost-type-in-ird? */
    /* sx: no, it is also used in rpc-reply of cost-map-service, see the augment statements near the end*/
    leaf cost-type-name {
      type cost-type-name;
    }
    leaf cost-mode {
      type cost-mode;
      description
        "Cost mode.";
    }
    leaf cost-metric {
      type cost-metric;
      description
        "Cost metric.";
    }
    leaf description {
      /* yry: How to indicate this is optional? */
      /* sx: I believe all leafs are optional unless specified as mandatory which I have not done yet... */
      type string;
      description
        "Optional description field.";
    }
    description
      "Cost type. RFC7285 Sec. 10.7." +
      " object {
          CostMetric cost-metric;
          CostMode   cost-mode;
          [JSONString description;]
        } CostType;";
  }

  typedef constraint {
    type string {
      pattern "(gt|ge|lt|le|eq) [0-9]+";
    }
    description
      "RFC7285 Sec. 11.3.2.3. The second part must be in the" +
      "same unit as cost-metric, IEEE 754 2008 floating point.";
  }

  typedef endpoint-property-type {
    type union {
      type resource-specific-endpoint-property;
      type global-endpoint-property;
    }
    description
      "Endpoint property type. RFC7285 Sec. 10.8.";
  }

  typedef resource-specific-endpoint-property {
    type string {
      length "3..97"; //len(resource-id) + 1 + len(global-property)
      pattern "[\w\-:@\.]+\.[\w\-:_]+"; // resource-id.property
      /* yry: is it possible to enforce reference to existence of id and prop? */
      /* sx: with string concatenation, I do not think that is possible in YANG 1.0 */
    }
    description
      "Resource-specific endpoint property.";
  }

  typedef global-endpoint-property {
    type union {
      type enumeration {
        enum pid {
          description "PID property.";
        }
        // other options here
      }
      type string {
        length "1..32";
        pattern "[\w\-:_]+"; // '.' is not allowed.
      }
    }
    description
      "Global endpoint property. RFC7285 Sec. 10.8.2." +
      "'priv:' for Private Use ";
  }

  typedef endpoint-property-value {
    type string;
    description
      "Endpoint property (value).";
  }

  typedef resource-id {
    type valid-id-string;
    description
      "Resource-ID.";
  }

  grouping version-tag {
    leaf resource-id {
      type resource-id;
    }
    leaf tag {
      type string {
        length "1..64";
        pattern "[!-~]+";
      }
      description
        "Tag. RFC7285 Sec. 10.3. U+0021-U+007E";
    }
    description
      "Version tag. Both resource-id and tag must be equal
       byte-for-byte. RFC7285 Sec. 10.3." +
      " object {
          ResourceID resource-id;
          JSONString tag;
        } VersionTag;";
  }

  grouping meta {
    choice dependent {
      // multiple vtags
      case dependent {
        list dependent-vtags {
          uses version-tag;
          description
            "Version tags.";
        }
      }
      case independent {
        container vtag {
          uses version-tag;
          description
            "Version tag.";
        }
      }
    }
    description
      "Meta information. RFC7285 Sec. 8.4.1." + 
      "object-map { JSONString -> JSONValue } ResponseMeta;";
  }

  typedef media-type {
    type union {
      type string {
        // TODO: restrict more? RFC 7285, Sec. 14.1?
        pattern "application/alto\-.*";   /* yry: it may not be always alto- */
      }
      type enumeration {
        enum alto-directory+json;
        enum alto-networkmap+json;
        enum alto-networkmapfilter+json;
        enum alto-costmap+json;
        enum alto-costmapfilter+json;
        enum alto-endpointprop+json;
        enum alto-endpointpropparams+json;
        enum alto-endpointcost+json;
        enum alto-endpointcostparams+json;
        enum alto-error+json;
      }
    }
  }

  typedef alto-cost {
    type decimal64 {
      fraction-digits 6;
    }
    description
      "ALTO costs, currently only integer values.";
  }

  /******************
   * DATA INSTANCES *
   ******************/

  /*
   * unfiltered network-maps, unfiltered cost-maps are all
   * instances of resource.
   *
   * IRD is also modeled as data.
   */
  list resource {
    config false;
    // ResponseEntityBase;
    // Note: resource-id for network/cost maps are in their meta,
    // see the augment statements below.
    container meta {
      uses meta;
    }
    leaf uri {
      type inet:uri;
    }
    leaf media-type {
      type media-type;
    }
  }

  /* network-map */
  augment "/resource" {
    when "./media-type = 'application/alto-networkmap+json' ";
    uses network-map;
  }

  grouping network-map {
    list network-map {
      /* yry: enforce completeness (RFC 7285/Section 11.2.2) of a network map ? 
         How about define a derived type, which is complete?*/
      key "pid";
      leaf pid {
        type pid-name;
      }
      uses endpoint-address-group;
      description
        "RFC7285 Sec. 11.2.1.6." + 
        " object-map {
            PIDName -> EndpointAddrGroup;
          } NetworkMapData;";
    }
    description
      "Network map. RFC7285 Sec. 11.2.1.6." +
      "object {
         NetworkMapData network-map;
       } InfoResourceNetworkMap : ResponseEntityBase;";
  }

  /* cost map */
  augment "/resource" {
    when "./media-type = 'application/alto-costmap+json' ";
    uses cost-map;
  }

  grouping cost-map {
    list cost-map {
      leaf src {
        type pid-name;
        description
          "Source PID.";
      }
      key "src";
      list dst-costs {
        leaf dst {
          type pid-name;
          description
            "Destination PID.";
        }
        key "dst";
        leaf cost {
          type alto-cost;
          description
            "Cost from source to destination.";
        }
        description
          "The list represents the inner part of the cost matrix." +
          "DstCosts. RFC7285 Sec. 11.2.3.6." +
          " object-map {
              PIDName -> JSONValue;
            } DstCosts;";
      }         
      description
        "The list represents the outer part of the cost matrix." +
        "CostMapData. RFC7285 Sec. 11.2.3.6." +
        " object-map {
            PIDName -> DstCosts;
          } CostMapData;";
    }
    description
      "Cost map. RFC7285 Sec. 11.2.3.6." +
      " object {
          CostMapData cost-map;
        } InfoResourceCostMap : ResponseEntityBase;";
  }

  container IRD {
    config false;
    leaf uri {
      type inet:uri;
    }
    leaf media-type {
      type media-type;
    }
    list resources {
      key resource-id;
      leaf resource-id {
        type resource-id;
        //TODO: ideally, this should be a leafref to the resource-id
        //in various resources, e.g. network-map/meta/vtag/resource-id
        //but this might need much more complicated conditioning.
        //Also need to try to enforce this resource-id matches the
        //uri and media-type of that resource. Not sure how to yet.
      }
      leaf uri {
        type leafref {
          path "/resource/uri";
        }
      }
      leaf media-type {
        type leafref {
          path "/resource/media-type";
        }
      }
      description
        "IRDResourceEntry. RFC7285 9.2.2." +
        " object {
            JSONString      uri;
            JSONString      media-type;
            [JSONString     accepts;]
            [Capabilities   capabilities;]
            [ResourceID     uses<0..*>;]
          } IRDResourceEntry;" +
        "IRDResourceEntries. RFC7285 9.2.2." +
        " object-map {
            ResourceID  -> IRDResourceEntry;
          } IRDResourceEntries;" +
        "InformationResourceDirectory. RFC7285 9.2.2." +
        " object {
            IRDResourceEntries resources;
          } InfoResourceDirectory : ResponseEntityBase;";
    }
  }

  /* meta */
  augment "/IRD" {
    container meta {
      uses meta;
      list cost-types {
        key "cost-type-name";
        uses cost-type;
        description
          "Cost type. RFC7285 Sec. 9.2.2." + 
          " object-map {
              JSONString -> CostType;
            } IRDMetaCostTypes;";
      }
      leaf default-alto-network-map {
        type leafref {
          path "../../../IRD/resources/resource-id";
        }
      }
    }
  }

  augment "/resource/meta" {
    when "../media-type = 'application/alto-costmap+json' ";
    container cost-type {
      uses cost-type;
      description
        "Cost type.";
    }
  }

  augment "/filtered-cost-map-service/output/filtered-cost-map-service/meta" {
    container cost-type {
      uses cost-type;
      description
        "Cost type.";
    }
  }

  augment "/endpoint-cost-service/output/endpoint-cost-service/meta" {
    container cost-type {
      uses cost-type;
      description
        "Cost type.";
    }
  }

  /* accepts (optional) */
  grouping accepts {
    leaf-list accepts {
      type media-type;
      min-elements 1;
    }
  }
  augment "/resource" {
    when ".";
    uses accepts;
  }
  augment "/IRD/resources" {
    when ".";
    leaf-list accepts {
      type leafref {
        path "/resource/accepts";
      }
    }
  }

  /* uses */
  grouping uses {
    leaf-list uses {
      type resource-id;
      min-elements 1;
    }
  }
  augment "/resource" {
    when "(./media-type = 'application/alto-endpointprop+json') " +
      "or (./media-type = 'application/alto-costmap+json') " +
      "or (./media-type = 'application/alto-networkmap+json' " +
      "and ./accepts = 'application/alto-networkmapfilter+json') " +
      "or (./media-type = 'application/alto-networkmap+json' " +
      "and ./accepts != '')";
    // the logic is that the following structures can be present ONLY 
    // when the above conditions are satisfied. Not sure how to place
    // different restrictions on different conditions.
    uses uses;
  }
  augment "/IRD/resources" {
    when "(./media-type = 'application/alto-endpointprop+json') " +
      "or (./media-type = 'application/alto-costmap+json') " +
      "or (./media-type = 'application/alto-networkmap+json' " +
      "and ./accepts = 'application/alto-networkmapfilter+json') " +
      "or (./media-type = 'application/alto-networkmap+json' " +
      "and ./accepts != '')";
    leaf-list uses {
      type leafref {
        path "/resource/uses";
      }
    }
  }

  /* capabilities */
  augment "/resource" {
    when "./media-type = 'application/alto-costmap+json' ";
    container capabilities {
      when "current()";
      leaf-list cost-type-names {
        type leafref {
          path "../../meta/cost-type/cost-type-name";
        }
        min-elements 1; // if added, capabilities becomes mandatory in cost-map.
        max-elements 1;
      }
      leaf-list prop-types {
        type endpoint-property-type;
      }
      description
        "CostMapCapabilities. RFC7285 Sec. 11.2.3.4." +
        " object {
            JSONString cost-type-names<1..1>;
          } CostMapCapabilities;";
      // TODO: model other CostMapCapabilities, if provided
    }
  }

  augment "/IRD/resources" {
    container capabilities {
      leaf cost-constraints {
        type boolean;
      }
      leaf-list cost-type-names {
        /*type leafref {
          path "/resource/capabilities/cost-type-names";
        }*/
        type cost-type-name;
      }
      leaf-list prop-types {
        type endpoint-property-type;
        /*type leafref {
          path "/resource/capabilities/prop-types";
        }*/
      }
    }
  }

  augment "/endpoint-property-service/output/endpoint-property-service" {
    leaf-list capabilities {
      when ".";
      type endpoint-property-type;
      min-elements 1;
      description
        "Sec. 11.4.1.4." +
        " object {
            EndpointPropertyType prop-types<1..*>;
          } EndpointPropertyCapabilities;";
    }
  }

  augment "/filtered-cost-map-service/output/filtered-cost-map-service" {
    container capabilities {
      when ".";
      leaf-list cost-type-names {
        type leafref {
          path "../../meta/cost-type/cost-type-name";
        }
        min-elements 1;
      }
      leaf cost-constraints {
        type boolean;
      }
      description
        "FilteredCostMapCapabilities. RFC7285 Sec. 11.3.2.4." +
        " object {
            JSONString cost-type-names<1..*>;
            JSONBool cost-constraints;
          } FilteredCostMapCapabilities;";
    // TODO: model other CostMapCapabilities, if provided
    }
  }

  /*******
   * RPC *
   *******/

  rpc endpoint-property-service {
    description
      "inquiries on properties of an endpoint";
    input {
      leaf-list properties {
        type endpoint-property-type;
        min-elements 1;
      }
      leaf-list endpoints {
        type endpoint-address;
        min-elements 1;
      }
      /*
      description
        " object {
            EndpointPropertyType  properties<1..*>;
            TypedEndpointAddr     endpoints<1..*>;
          } ReqEndpointProp;";
      */
    }
    output {
      container endpoint-property-service {
        container meta {
          uses meta;
        }
        list endpoint-properties {
          key pid;
          leaf pid {
            type endpoint-address;
          }
          list properties {
            key property-type;
            leaf property-type {
              type endpoint-property-type;
            }
            leaf property {
              type endpoint-property-value;
            }
            description
              "EndpointProps. RFC7285 Sec. 11.4.1.6." +
              " object {
                  EndpointPropertyType -> JSONValue;
                } EndpointProps;";
          }
          description
            "EndpointPropertyMapData. Sec. 11.4.1.6." +
            " object-map {
                TypedEndpointAddr -> EndpointProps;
              } EndpointPropertyMapData;";
        }
        description
          "InfoResourceEndpointProperties. Sec. 11.4.1.6." +
          " object {
              EndpointPropertyMapData endpoint-properties;
            } InfoResourceEndpointProperties : ResponseEntityBase;";
      }
    }
  }

  rpc filtered-network-map-service {
    description
      "inquiries on filtered network map";
    input {
      leaf-list pids {
        type pid-name;
      }
      leaf-list address-types {
        type endpoint-address-type;
      }
      /*
      description
        "ReqFilteredNetworkMap. RFC7285 Sec. 11.3.1.3." +
        " object {
            PIDName pids<0..*>;
            [AddressType address-types<0..*>;]
          } ReqFilteredNetworkMap;";
      */
    }
    output {
      container filtered-network-map-service {
        container meta {
          uses meta;
        }
        uses network-map;
      }
    }
  }

  rpc filtered-cost-map-service {
    input {
      container cost-type {
        uses cost-type;
        description
          "Cost type.";
      }
      leaf-list constraints {
        type constraint;
        description
          "RFC7285 Sec. 11.3.2.3.";
      }
      container pids {
        leaf-list srcs {
          type pid-name;
          description
            "Source endpoint addresses.";
        }
        leaf-list dsts {
          type pid-name;
          description
            "Destination endpoint addresses.";
        }
        description
          "PIDFilter: Endpoint addresses. RFC7285 Sec. 11.3.2.3." +
          " object {
              PIDName srcs<0..*>;
              PIDName dsts<0..*>;
            } PIDFilter;";
      }
      */
      // TODO: optional constraint JSON strings RFC7285 Sec. 11.3.2.3
      description
        "ReqFilteredCostMap. RFC7285 Sec. 11.3.2.3." +
        " object {
            CostType   cost-type;
            [JSONString constraints<0..*>;]
            [PIDFilter  pids;]
          } ReqFilteredCostMap;";
      */
    }
    output {
      container filtered-cost-map-service {
        container meta {
          uses meta;
          description
            "Meta information.";
        }
        uses cost-map;
      }
    }
  }

  rpc endpoint-cost-service {
    input {
      container cost-type {
        uses cost-type;
        description
          "Cost type.";
      }
      leaf-list constraints {
        type constraint;
        description
          "RFC7285 Sec. 11.5.1.3.";
      }
      container pids {
        leaf-list srcs {
          type endpoint-address;
          description
            "Source endpoint addresses.";
        }
        leaf-list dsts {
          type endpoint-address;
          description
            "Destination endpoint addresses.";
        }
        description
          " EndpointFilter: Endpoint addresses. RFC7285 Sec. 11.5.1.3." +
          " object {
              [TypedEndpointAddr srcs<0..*>;]
              [TypedEndpointAddr dsts<0..*>;]
            } EndpointFilter;";
      }
      /*
      description
        "ReqEndpointCostMap. RFC7285 Sec. 11.5.1.3." +
        " object {
            CostType          cost-type;
            [JSONString       constraints<0..*>;]
            EndpointFilter    endpoints;
          } ReqEndpointCostMap;";
      */
    }
    output {
      container endpoint-cost-service {
        container meta {
          uses meta;
          description
            "Meta information.";
        }
        list endpoint-cost-map {
          leaf src {
            type endpoint-address;
            description
              "Source endpoint address.";
          }
          key "src";
          list dst-costs {
            leaf dst {
              type endpoint-address;
              description
                  "Destination endpoint address.";
            }
            key "dst";
            leaf cost {
              type alto-cost;
                description
                  "Cost from source to destination.";
            }
            description
              "The list represents the inner part of the cost matrix." +
              "EndpointDstCosts. RFC7285 Sec. 11.5.1.6." +
              " object-map {
                  TypedEndpointAddr -> JSONValue;
                } EndpointDstCosts;";
          }
          description
            "The list represents the outer part of the cost matrix." +
            "EndpointCostMapData. RFC7285 Sec. 11.5.1.6." +
            " object {
                EndpointCostMapData endpoint-cost-map;
              } InfoResourceEndpointCostMap : ResponseEntityBase;
              object-map {
                TypedEndpointAddr -> EndpointDstCosts;
              } EndpointCostMapData;";
        }
      }
    }
  }


}
